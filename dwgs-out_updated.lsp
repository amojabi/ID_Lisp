(defun confirmation ()
	(if (equal (getkword "Did you save-as? Please confirm (Yes or No): ") "Yes")
		T
		(cancelMsg)
		)
	)

(defun cancelMsg()
	(alert "AutoLISP routine was cancelled.")
	(princ)
	)

(defun DestroyWarning ()
	(alert "If this file is an original BASE drawing file, Proceed now to do a SAVE-AS to a different temporary drawing file name.")
	)

(defun destroy_msg ()
	(alert "Be certain you have just done a SAVE-AS to a temp file and this drawing is NOT the original BASE plan cad file.

		All Layout Tabs with names not containing the letters CD or TEMP will be deleted from this drawing file. Rename any Layout Tabs to be saved prior to running this routine.

		DO NOT RUN THIS ROUTINE ON THE ORIGINAL *BASE CAD FILE !!!!
		This is your final reminder.")
	)

(defun BindXref ()
	(command "_.-xref" "Bind" "_All" "")
	)

(defun Delete_Layouts ()
	(setq a (layoutlist))
	(setq len (length a))
	(setq count 0)
	(setq DeleteLayoutLayers (ssget "X" (list '(0 . "LAYOUT") '(8 . "CD,TEMP"))))
	(repeat len
		(setq zz (nth count a))
		(setq zz_strcat (strcase zz))
		(if (not (wcmatch zz_strcat "CD,TEMP"))
			(command ".-layout" "delete" zz)
			(if (wcmatch zz_strcat "CD")
				(progn
					(command ".-layout" "set" zz)
					(command ".-erase" DeleteLayoutLayers)
					)
				)
			(setq count (1+ count))
			)
		)

	(defun main ()
		(DestroyWarning)
		(confirm "Please make sure you have saved-as before proceeding.")
		(destroy_msg)
		(if (confirmation)
			(progn
				(BindXref)
				(Delete_Layouts)
				(alert "AutoLISP routine completed successfully.")
				(princ)
				)
			)
		)

	(main)


;;;=====================================================================
;;;  Delete all TI & BOMA layers
;;;=====================================================================


(defun c:filesout (/ GoForIt)
	(initget 1 "Yes No")
	(setvar "cmdecho" 1)
	(DestroyWarning)
	(setq acadver (getvar "acadver"))
	(command "saveas" (setq dwgver (strcat acadver "")) "~")
	(destroy_msg)
	(setq GoForIt (confirmation))
	(if (= GoForIt "Yes")
		(progn
			(DestroyTI_BOMA)
			(setq GetMiscEnt (ssget "x"
				'((-4 . "<OR")
					(8 . "0*")
					(8 . "anno-dims")
					(-4 . "OR>")
					)
				))
			(if (/= nil GetMiscEnt)
				(command "erase" GetMiscEnt "")
				)
			(Delete_Layouts)
			(command "-purge" "layers" "" "n")
			(BindXref)
			(command "-purge" "b" "" "n")
			(command "xref" "detach" "id*")
			(command "-purge" "layers" "*" "n")
			(princ)
			)
		(cancelMsg)
		)
	)

(defun DestroyTI_BOMA (/ get_ti get_boma)
	(setvar "tilemode" 1)
	(command "layer" "thaw" "ti*" "")
	(command "layer" "Unlock" "ti*" "")
	(setq get_ti (ssget "x"
		'((0 . "insert")
			(-4 . "<OR")
			(2 . "ti*")
			(2 . "suite*")
			(-4 . "OR>")
			)
		)
	)
	(if (/= nil get_ti)
		(progn
			(command "erase" get_ti "")
			(command "-purge" "block" "ti*" "n")
			(command "-purge" "block" "suite*" "n")
			)
		)
	(command "layer" "thaw" "BOMA*,AREA*,TI*" "")
	(command "layer" "Unlock" "BOMA*,AREA*,TI*" "")
	(setq get_boma (ssget "x"
		'((-4 . "<OR")
			(8 . "BOMA*")
			(8 . "AREA*")
			(8 . "TI*")
			(-4 . "OR>")
			)
		)
	)
	(if (/= nil get_boma)
		(command "erase" get_boma "")
		)
	(command "-purge" "layers" "*" "n")
	)

;;;============================================================
;;; "Save-As All Total "as-built" (explode all TI Blocks first)
;;;============================================================

(defun ID_SaveAsAllBkgd (PlanType / GoForIt)
	(initget 1 "Yes No BKGD CONST CONSTELEC CONSTFINISH CONSTELECFINISH CONSTELECFINISHRCP CONSTRCP ELEC ELEC_RCP FINISH RCP")
	(setvar "cmdecho" 0)
	(setq SaveAs PlanType)
	(DestroyWarning)
	(setq acadver (getvar "acadver"))
	(command "saveas" (setq dwgver (strcat acadver "")) "~")
	(destroy_msg)
	(setq GoForIt (yes_or_no_p "Do you want to proceed? "))
	(alert GoForIt)
	(if GoForIt
		(progn
			(setvar "tilemode" 1)
			(command "layer" "thaw" "ti*" "")
			(command "layer" "Unlock" "ti*" "")
			(setq get_ti (ssget "x"
				'((0 . "insert")
					(-4 . "<OR")
					(2 . "ti_")
					(2 . "suite")
					(-4 . "OR>")
					)
				)
			)
			(if get_ti
				(progn
					(setq count 0)
					(setq get_ti_Len (sslength get_ti))
					(repeat get_ti_len
						(command "_.Explode" (ssname get_ti count))
						(setq count (+ 1 count))
						)
					(command "-purge" "block" "ti*,suite*" "n")
					)
				)
			(DestroyTI_BOMA)
			(Destroy_PlanLyr)
			(command "-purge" "layers" "*" "n")
			)
		)
	(princ)
	)

;;;=====================================================
;;; "Save-As *plans routine
;;;=====================================================

(defun ID_SaveAsDemo (PlanType / GoForIt)
	(setvar "cmdecho" 0)
	(setq SaveAs PlanType)
	(DestroyWarning)
	(setq acadver (getvar "acadver"))
	(command "saveas" (setq dwgver (strcat acadver "")) "~")
	(setq GoForIt (confirmation))
	(destroy_msg)
	(if (= GoForIt "Yes")
		(progn
			(DestroyTI_BOMA)
			(Destroy_PlanLyrDemo)
			)
		)
	(princ)
	)

;;;=====================================================
;;; "Save-As *plans routine
;;;=====================================================
(defun ID_SaveAsNewName (PlanType / GoForIt)
	(setvar "cmdecho" 0)
	(setq SaveAs PlanType)
	(DestroyWarning)
	(setq acadver (getvar "acadver"))
	(command "saveas" (setq dwgver (strcat acadver "")) "~")
	(setq GoForIt (confirmation))
	(destroy_msg)
	(if (= GoForIt "Yes")
		(progn
			(DestroyTI_BOMA)
			(Destroy_PlanLyr)
			)
		)
	(princ)
	)

;;;======================================================
;;; Sub-routine for the "Save-AS" plans routines. These are being called from above
;;;;;;;;;;;;;;;;;;;;SAVEAS WITHOUT DEMO LAYERS;;;;;;;;;;;;;;;;;;;;;;;;;

(defun Destroy_PlanLyr (/ GetAll GetExstNewwOnly Delete)
	(command "layer" "thaw" "*" "")
	(command "layer" "Unlock" "*" "")
	(setq GetAll (ssget "x"))
	(setq GetExstNewwOnly (ssget "x"
		'((-4 . "<OR")
			(8 . "*EXST*")
			(8 . "*NEWW*")
			(8 . "C-*")
			(8 . "E-*")
			(8 . "F-*")
			(8 . "R-*")
			(8 . "*LITE-DEMO*")
			(8 . "*HVAC-DEMO*")
			(8 . "*TTLBLK*")
			(8 . "G-ANNO-*")
			(-4 . "OR>")
			)
		))
	(if (/= nil GetExstNewwOnly)
		(command "erase" GetAll "r" GetExstNewwOnly "")
		)
	(if (= SaveAS "BKGD")
		(progn
			(setq Delete (ssget "x"
				'((-4 . "<OR")
					(8 . "C-*")
					(8 . "E-*")
					(8 . "F-*")
					(8 . "R-*")
					(8 . "*DEMO*")
					(8 . "*CLNG*")
					(8 . "*HEAD*")
					(8 . "*HVAC*")
					(8 . "*LITE*")
					(8 . "*SPRN*")
					(8 . "*FLOR-PATT*")
					(8 . "*POWR*")
					(8 . "*FURN*")
					(8 . "*EQPM*")
					(8 . "*RMTAG*")
					(8 . "*PLMB*")
					(-4 . "OR>")
					)
				)
			)
			(setq DeleteLayoutLayers (ssget "x"
				'((-4 . "<OR")
					(8 . "D-*")
					(8 . "C-*")
					(8 . "E-*")
					(8 . "F-*")
					(8 . "R-*")
					(-4 . "OR>")
					)
				)
			)
			)
		)
	(if (= SaveAS "CONST")
		(progn
			(setq Delete (ssget "x"
				'((-4 . "<OR")
					(8 . "E-*")
					(8 . "F-*")
					(8 . "R-*")
					(8 . "*DEMO*")
					(8 . "*CLNG*")
					(8 . "*HEAD*")
					(8 . "*HVAC*")
					(8 . "*LITE*")
					(8 . "*SPRN*")
					(8 . "*FLOR-PATT*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "D-*")
					(8 . "E-*")
					(8 . "F-*")
					(8 . "R-*")
					(-4 . "OR>")
					)
				)
			)
			)
		)
	(if (= SaveAS "CONSTELEC")
		(progn
			(setq Delete (ssget "x"
				'((-4 . "<OR")
					(8 . "F-*")
					(8 . "R-*")
					(8 . "*DEMO*")
					(8 . "*CLNG*")
					(8 . "*HEAD*")
					(8 . "*HVAC*")
					(8 . "*LITE*")
					(8 . "*SPRN*")
					(8 . "*FLOR-PATT*")
					(-4 . "OR>")
					)
				)
			)
			(setq DeleteLayoutLayers (ssget "x"
				'((-4 . "<OR")
					(8 . "D-*")
					(8 . "F-*")
					(8 . "R-*")
					(-4 . "OR>")
					)
				)
			)
			)
		)
	(if (= SaveAS "CONSTFINISH")
		(progn
			(setq Delete (ssget "x"
				'((-4 . "<OR")
					(8 . "E-*")
					(8 . "R-*")
					(8 . "*DEMO*")
					(8 . "*CLNG*")
					(8 . "*HEAD*")
					(8 . "*HVAC*")
					(8 . "*LITE*")
					(8 . "*SPRN*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "D-*")
					(8 . "E-*")
					(8 . "R-*")
					(-4 . "OR>")
					)
				)
			)
			)
		)
	(if (= SaveAS "CONSTELECFINISH")
		(progn
			(setq Delete (ssget "x"
				'((-4 . "<OR")
					(8 . "R-*")
					(8 . "*DEMO*")
					(8 . "*CLNG*")
					(8 . "*HEAD*")
					(8 . "*HVAC*")
					(8 . "*LITE*")
					(8 . "*SPRN*")
					(-4 . "OR>")
					)
				)
			)
			(setq DeleteLayoutLayers (ssget "x"
				'((-4 . "<OR")
					(8 . "D-*")
					(8 . "R-*")
					(-4 . "OR>")
					)
				)
			)
			)
		)
	(if (= SaveAS "CONSTELECFINISHRCP")
		(progn
			(setq Delete (ssget "x"
				'((-4 . "<OR")
					(8 . "*WALL*DEMO*")
					(-4 . "OR>")
					)
				)
			)
			(setq DeleteLayoutLayers (ssget "x"
				'((-4 . "<OR")
					(8 . "D-*")
					(-4 . "OR>")
					)
				)
			)
			)
		)
	(if (= SaveAS "CONSTRCP")
		(progn
			(setq Delete (ssget "x"
				'((-4 . "<OR")
					(8 . "E-*")
					(8 . "F-*")
					(8 . "*FLOR-PATT*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "D-*")
					(8 . "E-*")
					(8 . "F-*")
					(-4 . "OR>")
					)
				)
			)
			)
		) 
	(if (= SaveAS "ELEC")
		(progn
			(setq Delete (ssget "x"
				'((-4 . "<OR")
					(8 . "C-*")
					(8 . "F-*")
					(8 . "R-*")
					(8 . "*DEMO*")
					(8 . "*CLNG*")
					(8 . "*HEAD*")
					(8 . "*HVAC*")
					(8 . "*LITE*")
					(8 . "*PLMB-UNDR*")
					(8 . "*PLMB-WATR*")
					(8 . "*SPRN*")
					(8 . "*FLOR-PATT*")
					(8 . "*-SYMB-*")
					(8 . "*-FLOR-SIGN-*")
					(-4 . "OR>")
					)
				)
			)
			(setq DeleteLayoutLayers (ssget "x"
				'((-4 . "<OR")
					(8 . "D-*")
					(8 . "C-*")
					(8 . "F-*")
					(8 . "R-*")
					(-4 . "OR>")
					)
				)
			)
			)
		)

	(if (= SaveAS "ELEC_RCP")
		(progn
			(setq Delete (ssget "x"
				'((-4 . "<OR")
					(8 . "C-*")
					(8 . "F-*")
					(8 . "*FLOR-PATT*")
					(-4 . "OR>")
					)
				)
			)
			(setq DeleteLayoutLayers (ssget "x"
				'((-4 . "<OR")
					(8 . "D-*")
					(8 . "C-*")
					(8 . "F-*")
					(-4 . "OR>")
					)
				)
			)
			)
		)

	(if (= SaveAS "FINISH")
		(progn
			(setq Delete (ssget "x"
				'((-4 . "<OR")
					(8 . "C-*")
					(8 . "D-*")
					(8 . "E-*")
					(8 . "R-*")
					(8 . "*DEMO*")
					(8 . "*CLNG*")
					(8 . "*HEAD*")
					(8 . "*HVAC*")
					(8 . "*LITE*")
					(8 . "*PLMB*")
					(8 . "*SPRN*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "D-*")
					(8 . "E-*")
					(8 . "C-*")
					(8 . "R-*")
					(-4 . "OR>")
					)
				)
			)
			)
		)
	(if (= SaveAs "RCP")
		(progn
			(setq Delete (ssget "x"
				'((-4 . "<OR")
					(8 . "C-*")
					(8 . "E-*")
					(8 . "F-*")
					(8 . "*POWR-EXST*")
					(8 . "*POWR-NEWW*")
					(8 . "*WDWK*")
					(8 . "*FURN*")
					(8 . "*PFIX*")
					(8 . "*PLMB*")
					(8 . "*EQPM-EXST")
					(8 . "*EQPM-NEWW")
					(8 . "*FLOR*")
					(8 . "*-SITE-*")
					(-4 . "OR>")
					)
				)
			)
			(setq DeleteLayoutLayers (ssget "x"
				'((-4 . "<OR")
					(8 . "D-*")
					(8 . "C-*")
					(8 . "F-*")
					(8 . "E-*")
					(-4 . "OR>")
					)
				)
			)
			)
		)

	(if (/= nil Delete)
		(command "erase" Delete "")
		)
	(Delete_Layouts)
	(command "-purge" "layers" "*" "n")
	(BindXref)
	(command "-purge" "b" "*" "n")
	(command "xref" "detach" "id*")
	(command "-purge" "layers" "*" "n")
	)

;;;;;;;;;;;;;;;;;;;;;;; SAVEAS WITH DEMO LAYERS ;;;;;;;;;;;;;;;;;;;;;;;;;;;;;

(defun Destroy_PlanLyrDemo (/ GetAll GetExstNewwOnly Delete)
	(command "layer" "thaw" "*" "")
	(command "layer" "Unlock" "*" "")
	(BindXref)
	(setq GetAll (ssget "x"))
	(setq GetExstNewwOnly (ssget "x"
		'((-4 . "<OR")
			(8 . "D-*")
			(8 . "C-*")
			(8 . "E-*")
			(8 . "F-*")
			(8 . "R-*")
			(8 . "*EXST*")
			(8 . "*DEMO*")
			(8 . "*NEWW*")
			(8 . "*LITE-DEMO*")
			(8 . "*TTLBLK*")
			(8 . "G-ANNO-TTLB*")
			(-4 . "OR>")
			)
		))
	(if (/= nil GetExstNewwOnly)
		(command "erase" GetAll "r" GetExstNewwOnly "")
		)


	(if (= SaveAS "DEMO")
		(progn
			(setq Delete (ssget "x"
				'((-4 . "<OR")
					(8 . "C-*")
					(8 . "E-*")
					(8 . "F-*")
					(8 . "R-*")
					(8 . "*NEWW*")
					(8 . "*POWR*-EXST*")
					(8 . "I-CLNG*")
					(8 . "A-CLNG*")
					(8 . "*HEAD*")
					(8 . "*HVAC*")
					(8 . "*LITE*")
					(8 . "*OVHD*")
					(8 . "*SPRN*")
					(8 . "*FLOR-PATT*")
					(-4 . "OR>")
					)
				)
			)
			(setq DeleteLayoutLayers (ssget "x"
				'((-4 . "<OR")
					(8 . "E-*")
					(8 . "C-*")
					(8 . "F-*")
					(8 . "R-*")
					(-4 . "OR>")
					)
				)
			)
			)
		)
	(if (= SaveAS "DEMOCONST")
		(progn
			(setq Delete (ssget "x"
				'((-4 . "<OR")
					(8 . "E-*")
					(8 . "F-*")
					(8 . "R-*")
					(8 . "*CLNG*")
					(8 . "*HEAD*")
					(8 . "*HVAC*")
					(8 . "*LITE*")
					(8 . "*SPRN*")
					(8 . "*FLOR-PATT*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "E-*")
					(8 . "F-*")
					(8 . "R-*")
					(-4 . "OR>")
					)
				)
			)
			)
		)
	(if (= SaveAS "DEMOCONSTELEC")
		(progn
			(setq Delete (ssget "x"
				'((-4 . "<OR")
					(8 . "F-*")
					(8 . "R-*")
					(8 . "*CLNG*")
					(8 . "*HEAD*")
					(8 . "*HVAC*")
					(8 . "*LITE*")
					(8 . "*SPRN*")
					(8 . "*FLOR-PATT*")
					(-4 . "OR>")
					)
				)
			)
			(setq DeleteLayoutLayers (ssget "x"
				'((-4 . "<OR")
					(8 . "F-*")
					(8 . "R-*")
					(-4 . "OR>")
					)
				)
			)
			)
		)
	(if (= SaveAS "DEMOCONSTFINISH")
		(progn
			(setq Delete (ssget "x"
				'((-4 . "<OR")
					(8 . "E-*")
					(8 . "R-*")
					(8 . "*CLNG*")
					(8 . "*HEAD*")
					(8 . "*HVAC*")
					(8 . "*LITE*")
					(8 . "*SPRN*")
					(8 . "*POWR-EXST*")
					(8 . "*POWR-NEWW*")
					(8 . "*FURN*")
					(8 . "*EQPM*")
					(-4 . "OR>")
					)
				)
			)
			(setq DeleteLayoutLayers (ssget "x"
				'((-4 . "<OR")
					(8 . "E-*")
					(8 . "R-*")
					(-4 . "OR>")
					)
				)
			)
			)
		)
	(if (= SaveAS "DEMOCONSTELECFINISH")
		(progn
			(setq Delete (ssget "x"
				'((-4 . "<OR")
					(8 . "R-*")
					(8 . "*CLNG*")
					(8 . "*HEAD*")
					(8 . "*HVAC*")
					(8 . "*LITE*")
					(8 . "*SPRN*")
					(-4 . "OR>")
					)
				)
			)
			(setq DeleteLayoutLayers (ssget "x"
				'((-4 . "<OR")
					(8 . "R-*")
					(-4 . "OR>")
					)
				)
			)
			)
		)
	(if (/= nil Delete)
		(command "erase" Delete "")
		)
	(Delete_Layouts)

	(command "-purge" "layers" "*" "n")
	(command "-purge" "b" "*" "n")
	(command "xref" "detach" "id*")
	(command "-purge" "layers" "*" "n")
	)

;;;=================================================================
;;;;;;;;;;Function to convert all dynamic blocks to anonymous blocks;;;;;;;;;;;;;;;;;;;;;
;;;==================================================================
(defun DynamicBlk_to_AnonymousBlk ()
	(vl-load-com)
	(command "layer" "thaw" "" "")
	(command "layer" "Unlock" "" "")
	(setq ssl (ssget "x" '((0 . "insert"))))
	(setq len (sslength ssl))
	(setq count 0)
	(repeat len
		(setq entget_ssname (entget (ssname ssl count)))
		(setq x-blk-en (cdr (car entget_ssname)))
		(setq obj (vlax-ename->vla-object x-blk-en))
		(if (= (vlax-get-property obj 'isdynamicblock) :vlax-true)
			(progn
				(setq x-blk-obj (vlax-ename->vla-object x-blk-en))
				(vla-ConvertToAnonymousBlock x-blk-obj)
				)
			)
		(setq count (1+ count))
		)
	(command "-purge" "blocks" "*" "n")
	)

(defun DBlk_to_ABlk ()
	(command ".undo" "BEgin")
	(DynamicBlk_to_AnonymousBlk)
	(command ".undo" "End")
	(alert "WARNING - This routine just converted ALL Dynamic BLocks to Anonymous Blocks in this current file. UNDO NOW if this is not what you wanted.")
	)

;;;;;;;;;;;;;;;;;;;;;;;;;;;;;;;;;;;;;;;;;;;;;;;;;;;;;;;;;;;;;;;;;;;;;;;;;;;;;;;
